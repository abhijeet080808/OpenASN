-- NameForm
TestModule1 { abc def }
DEFINITIONS
::=
BEGIN
END

-- DefinitiveNumberForm
TestModule2 { 1 2 }
DEFINITIONS
::=
BEGIN
END

-- DefinitiveNameAndNumberForm
TestModule3 { abc(1) def(2) }
DEFINITIONS
::=
BEGIN
END

-- DefinitiveOIDandIRI
TestModule4 { 1 2 } "/1/3/6/1/4/1/343"
DEFINITIONS
::=
BEGIN
END

TestModule5
DEFINITIONS
::=
BEGIN
EXPORTS ALL;
IMPORTS TypeRef1, TypeRef2, valueRef1, valueRef2 FROM ModuleRef;
Bool                  ::= BOOLEAN
END

TestModule6
DEFINITIONS
::=
BEGIN
EXPORTS TypeRef1, TypeRef2, valueRef1, valueRef2;
-- ObjectIdentifierValue
IMPORTS TypeRef1, TypeRef2, valueRef1, valueRef2 FROM ModuleRef {
  abc(1) xyz(2)
};
Bool                  ::= BOOLEAN
END

TestModule7
DEFINITIONS
::=
BEGIN
-- DefinedValue
IMPORTS TypeRef1, TypeRef2, valueRef1, valueRef2 FROM ModuleRef valueRef;
Bool                  ::= BOOLEAN
END

--------------------------------------------------------------------------------

TestModule
DEFINITIONS
-- EncodingReferenceDefault
TAG INSTRUCTIONS
-- TagDefault
AUTOMATIC TAGS
-- ExtensionDefault
EXTENSIBILITY IMPLIED
::=
BEGIN

Bool                  ::= BOOLEAN
BitStr1               ::= BIT STRING { a(0), b(1), c(100) }
BitStr2               ::= BIT STRING
CharStr1              ::= BMPString
CharStr2              ::= GeneralString
CharStr3              ::= GraphicString
CharStr4              ::= IA5String
CharStr5              ::= ISO646String
CharStr6              ::= NumericString
CharStr7              ::= PrintableString
CharStr8              ::= TeletexString
CharStr9              ::= T61String
CharStr10             ::= UniversalString
CharStr11             ::= UTF8String
CharStr12             ::= VideotexString
CharStr13             ::= VisibleString
CharStr14             ::= CHARACTER STRING

Choice                ::= CHOICE {
  chInt                 INTEGER,
  chBool                BOOLEAN
}

Date                  ::= DATE
DateTime              ::= DATE-TIME
Duration              ::= DURATION
EmbeddedPDV           ::= EMBEDDED PDV
Enumerated1           ::= ENUMERATED { a, b, c, d }
Enumerated2           ::= ENUMERATED { w(-1), x(0), y(1), z(2) }
External              ::= EXTERNAL
Int1                  ::= INTEGER
Int2                  ::= INTEGER { w(-1), x(0), y(1), z(2) }
Iri                   ::= OID-IRI
Null                  ::= NULL
ObjId                 ::= OBJECT IDENTIFIER
OctetStr              ::= OCTET STRING
Real                  ::= REAL
RelativeIri           ::= RELATIVE-OID-IRI
RelativeOid           ::= RELATIVE-OID

Sequence              ::= SEQUENCE {
  seqBool               BOOLEAN,
  seqBitStr1            BIT STRING { a(0), b(1), c(100) },
  seqBitStr2            BIT STRING,
  seqBitStr3            BIT STRING DEFAULT '1010'B,
  seqBitStr4            BIT STRING DEFAULT { abc, def },
  seqBitStr5            BIT STRING DEFAULT CONTAINING '00FF'H,
  seqCharStr1           BMPString,
  seqCharStr2           GeneralString,
  seqCharStr3           GraphicString,
  seqCharStr4           IA5String,
  -- RestrictedCharacterStringValue->Tuple
  seqCharStr4Tuple      IA5String DEFAULT { 2, 3 },
  seqCharStr5           ISO646String,
  seqCharStr6           NumericString,
  seqCharStr7           PrintableString,
  seqCharStr8           TeletexString,
  seqCharStr9           T61String,
  seqCharStr10          UniversalString,
  -- RestrictedCharacterStringValue->cstring
  seqCharStr10Cstr      UniversalString DEFAULT "ABCD",
  -- RestrictedCharacterStringValue->Quadruple
  seqCharStr10Quad      UniversalString DEFAULT { 10, 11, 12, 13 },
  -- RestrictedCharacterStringValue->CharacterStringList->cstring
  seqCharStr10StrList   UniversalString DEFAULT { "ABCD", "DEFG" },
  -- RestrictedCharacterStringValue->CharacterStringList->Quadruple
  seqCharStr10StrList   UniversalString DEFAULT {
                          { 10, 11, 12, 13 },
                          { 14, 15, 16, 17 }
                        },
  -- RestrictedCharacterStringValue->CharacterStringList->DefinedValue
  seqCharStr10StrList   UniversalString DEFAULT { abcd, defg },
  seqCharStr11          UTF8String,
  seqCharStr12          VideotexString,
  seqCharStr13          VisibleString,
  seqCharStr14          CHARACTER STRING,
  -- TODO UnrestrictedCharacterStringValue, NamedValue
  seqCharStr14StrVal    CHARACTER STRING DEFAULT {
                          --identification presentation-context-id:5,
                          string-value '66'H
                        },
  seqCh1                CHOICE { i INTEGER, b BOOLEAN },
  seqCh2                CHOICE { i INTEGER, b BOOLEAN } DEFAULT b : TRUE,
  seqDate               DATE,
  seqDateTime           DATE-TIME,
  seqDuration           DURATION,
  seqEmbeddedPDV        EMBEDDED PDV,
  -- TODO EmbeddedPDVValue
  seqEmbeddedPDVVal     EMBEDDED PDV DEFAULT {
                          --identification presentation-context-id:5,
                          data-value '66'H
                        },
  seqEnumerated1        ENUMERATED { a, b, c, d },
  seqEnumerated2        ENUMERATED { w(-1), x(0), y(1), z(2) },
  seqEnumeratedVal      ENUMERATED { a, b, c, d } DEFAULT a,
  seqInt1               INTEGER,
  seqInt2               INTEGER { w(-1), x(0), y(1), z(2) },
  seqIri                OID-IRI,
  -- From http://oid-info.com/get/1.3.6.1.4.1.343
  seqIriVal1            OID-IRI DEFAULT "/1/3/6/1/4/1/343",
  seqIriVal2            OID-IRI DEFAULT
                          "/ISO/Identified-Organization/6/1/4/1/343",
  seqNull               NULL,
  seqNullVal            NULL DEFAULT NULL,
  seqObjId              OBJECT IDENTIFIER,
  seqObjIdVal1          OBJECT IDENTIFIER DEFAULT { Abc.abc 1 },
  seqObjIdVal2          OBJECT IDENTIFIER DEFAULT { iso(1) 3 },
  seqObjIdVal3          OBJECT IDENTIFIER DEFAULT {
                          iso
                          identified-organization
                        },
  seqObjIdVal4          OBJECT IDENTIFIER DEFAULT {
                          iso(1)
                          identified-organization(3)
                        },
  seqOctetStr           OCTET STRING,
  seqOctetStrVal1       OCTET STRING DEFAULT '01101100'B,
  seqOctetStrVal2       OCTET STRING DEFAULT 'ABCD1100'H,
  seqOctetStrVal3       OCTET STRING DEFAULT CONTAINING 'ABCD1100'H,
  seqReal               REAL,
-- Simple numbers such as 10 etc are also parsed as Realnumber
  seqRealVal1           REAL DEFAULT 0e1,
  seqRealVal2           REAL DEFAULT 0.e1,
  seqRealVal3           REAL DEFAULT 0.1e1,
  seqRealVal4           REAL DEFAULT 0E1,
  seqRealVal5           REAL DEFAULT 0.E1,
  seqRealVal6           REAL DEFAULT 0.1E1,
  seqRealVal7           REAL DEFAULT 0e+1,
  seqRealVal8           REAL DEFAULT 0.e+1,
  seqRealVal9           REAL DEFAULT 0.1e+1,
  seqRealVal10          REAL DEFAULT 0e-1,
  seqRealVal11          REAL DEFAULT 0.e-1,
  seqRealVal12          REAL DEFAULT 0.1e-1,
  seqRealVal13          REAL DEFAULT 10e0,
  seqRealVal14          REAL DEFAULT 10.e0,
  seqRealVal15          REAL DEFAULT 10.1e0,
  seqRealVal16          REAL DEFAULT 10e10,
  seqRealVal17          REAL DEFAULT 10.e10,
  seqRealVal18          REAL DEFAULT 10.1e10,
  seqRealVal19          REAL DEFAULT -0e1,
  seqRealVal20          REAL DEFAULT -0.e1,
  seqRealVal21          REAL DEFAULT -0.1e1,
  seqRealVal21          REAL DEFAULT -0E1,
  seqRealVal23          REAL DEFAULT -0.E1,
  seqRealVal24          REAL DEFAULT -0.1E1,
  seqRealVal25          REAL DEFAULT -0e+1,
  seqRealVal26          REAL DEFAULT -0.e+1,
  seqRealVal27          REAL DEFAULT -0.1e+1,
  seqRealVal28          REAL DEFAULT -0e-1,
  seqRealVal29          REAL DEFAULT -0.e-1,
  seqRealVal30          REAL DEFAULT -0.1e-1,
  seqRealVal31          REAL DEFAULT -10e0,
  seqRealVal32          REAL DEFAULT -10.e0,
  seqRealVal33          REAL DEFAULT -10.1e0,
  seqRealVal34          REAL DEFAULT -10e10,
  seqRealVal35          REAL DEFAULT -10.e10,
  seqRealVal36          REAL DEFAULT -10.1e10,
  seqRealVal37          REAL DEFAULT { i 10.e0, j 10.e1, k -10.5e1 },
  seqRealVal38          REAL DEFAULT { i PLUS-INFINITY, j MINUS-INFINITY },
  seqRealVal39          REAL DEFAULT NOT-A-NUMBER,
  seqRelativeIri        RELATIVE-OID-IRI,
  seqRelativeIriVal1    RELATIVE-OID-IRI DEFAULT "3/6/1/4/1/343",
  seqRelativeIriVal2    RELATIVE-OID-IRI DEFAULT
                          "Identified-Organization/6/1/4/1/343",
  seqRelativeOid        RELATIVE-OID,
  seqRelativeOidVal1    RELATIVE-OID DEFAULT { iso(1) 3 Abc.abc },
  seqSeqVal1            SEQUENCE { i INTEGER, j INTEGER } DEFAULT { i -1, j 0 },
  seqSeqOf1             SEQUENCE OF INTEGER,
  seqSeqOf2             SEQUENCE OF INTEGER { w(-1), x(0), y(1), z(2) },
  seqSeqOf3             SEQUENCE OF seqSeqOf3Int INTEGER {
                          w(-1),
                          x(0),
                          y(1),
                          z(2)
                        },
  seqSeqOfVal1          SEQUENCE OF INTEGER DEFAULT { },
  seqSeqOfVal2          SEQUENCE OF INTEGER DEFAULT { w -1, x 0, y 1, z 2 },
  seqSeqOfVal3          SEQUENCE OF INTEGER DEFAULT { -1, 0, 1, 2 }
}

Sequence1             ::= SEQUENCE {
  COMPONENTS OF Sequence,
  seq1Int               INTEGER
}

SeqOf1                ::= SEQUENCE OF INTEGER
SeqOf2                ::= SEQUENCE OF INTEGER { w(-1), x(0), y(1), z(2) }
SeqOf3                ::= SEQUENCE OF seqOf3Int INTEGER {
                            w(-1),
                            x(0),
                            y(1),
                            z(2)
                          }

Set                   ::= SET {
  setBool               BOOLEAN,
  setBitStr1            BIT STRING { a(0), b(1), c(100) }
}

SetOf1                ::= SET OF INTEGER
SetOf2                ::= SET OF INTEGER { w(-1), x(0), y(1), z(2) }
SetOf3                ::= SET OF prefSetOf3Int INTEGER {
                            w(-1),
                            x(0),
                            y(1),
                            z(2)
                          }
Prefixed1             ::= [TAG : APPLICATION 5] IMPLICIT INTEGER
Prefixed2             ::= [PRIVATE 5] EXPLICIT INTEGER
Prefixed3             ::= [5] INTEGER
Prefixed4             ::= [PrefAbcModule.prefExtValueRef] INTEGER {
                            w(-1),
                            x(0),
                            y(1),
                            z(2)
                          }
Prefixed5             ::= [localValueRef] SET OF INTEGER {
                            w(-1),
                            x(0),
                            y(1),
                            z(2)
                          }
Prefixed6             ::= [TAG :] INTEGER
Time                  ::= TIME
TimeOfDay             ::= TIME-OF-DAY

DefinedType1          ::= DefAbcModule.DefExtTyperef
DefinedType2          ::= Prefixed1
UsefulType1           ::= GeneralizedTime
UsefulType2           ::= UTCTime
UsefulType3           ::= ObjectDescriptor

SelectionType         ::= chInt < Choice

-- TODO check precedence of EXCEPT ^ | 50.1 note 2
--SingleValue
SvConstrainedType1    ::= BOOLEAN (TRUE)
-- Two constraints (recursive)
SvConstrainedType2    ::= BOOLEAN (TRUE) (TRUE)
SvConstrainedType3    ::= BOOLEAN (TRUE ^ FALSE EXCEPT TRUE)
SvConstrainedType4    ::= BOOLEAN (TRUE | FALSE EXCEPT FALSE)
SvConstrainedType5    ::= BOOLEAN (TRUE ^ FALSE | FALSE ^ TRUE EXCEPT FALSE)
SvConstrainedType6    ::= BOOLEAN (TRUE , ... )
SvConstrainedType7    ::= BOOLEAN (TRUE , ... ! BOOLEAN : FALSE)
SvConstrainedType8    ::= BOOLEAN (TRUE , ... , FALSE)
SvConstrainedType9    ::= BOOLEAN (ALL EXCEPT TRUE)
SvConstrainedType10   ::= BOOLEAN (TRUE , ... , ALL EXCEPT FALSE)
SvConstrainedType11   ::= BOOLEAN (TRUE , ... , FALSE ! BOOLEAN : FALSE)
SvConstrainedType12   ::= BOOLEAN (TRUE , ... , FALSE EXCEPT TRUE ! BOOLEAN : FALSE)
SvConstrainedType13   ::= BIT STRING ('1100 0101'B | 'ABCD 1010'H)

--ContainedSubtype
CsConstrainedType1    ::= BOOLEAN (INCLUDES BOOLEAN)
CsConstrainedType2    ::= BOOLEAN (BOOLEAN)

--ValueRange
VrConstrainedType1    ::= BOOLEAN (MIN..MAX)
VrConstrainedType2    ::= INTEGER (-100..100)

--SizeConstraint
ScConstrainedType1    ::= BIT STRING (SIZE (10))
ScConstrainedType2    ::= BIT STRING (SIZE (0..10))

--PermittedAlphabet
-- TODO Change to meaningful constraints
PaConstrainedType1    ::= NumericString (FROM (TRUE | FALSE | TRUE))
PaConstrainedType2    ::= NumericString (BOOLEAN (INCLUDES BOOLEAN))
PaConstrainedType3    ::= NumericString (INTEGER (-100..100))
PaConstrainedType4    ::= NumericString (BIT STRING (SIZE (0..10)))

--TypeConstraint
TcConstrainedType1    ::= NumericString (BOOLEAN | INTEGER)

--InnerTypeConstraints
-- https://www.obj-sys.com/asn1tutorial/node18.html
ItcSeqOf1             ::= SEQUENCE OF INTEGER
-- Can only be applied to restrict set-of, sequence-of types
ItcConstrainedType1   ::= ItcSeqOf1 (WITH COMPONENT (-100..100))
ItcSeq1               ::= SEQUENCE {
  a                     BOOLEAN DEFAULT TRUE,
  b                     INTEGER OPTIONAL
}

ItcConstrainedType2   ::= ItcSeq1 (WITH COMPONENTS {
                            a (TRUE | FALSE),
                            b
                          })
-- Can only be applied to restrict set, sequence and choice types
ItcConstrainedType3   ::= ItcSeq1 (WITH COMPONENTS {
                            ...,
                            a (TRUE | FALSE),
                            b ABSENT
                          })

--PatternConstraint
PcConstrainedType1    ::= BOOLEAN (PATTERN TRUE)

--PropertySettings
PsConstrainedType1    ::= DATE (SETTINGS "Basic=Date Date=YMD")
PsConstrainedType2    ::= TIME (SETTINGS "Midnight=Start")

--------------------------------------------------------------------------------

-- TODO more examples
valRefBool BOOLEAN          ::= TRUE
valRefInt  INTEGER          ::= 1

--------------------------------------------------------------------------------

-- TODO more examples
ValSetTypeRef1 BOOLEAN      ::= { TRUE,..., FALSE }
ValSetTypeRef2 BOOLEAN      ::= { TRUE,... }
ValSetTypeRef3 BOOLEAN      ::= { TRUE }

END
