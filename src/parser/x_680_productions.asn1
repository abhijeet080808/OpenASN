--------------------------------
-- Rec. ITU-T X.680 (08/2015) --
--------------------------------

-- Productions may be annotated with the below tags as required -
--
-- LOCAL ADDITION
-- This production is not present in spec and is added locally to facilicate
-- parsing. Eg DEFINITIONS, BEGIN, END, ConstraintList.
--
-- LOCAL MODIFICATION
-- Modified production to facilicate parsing. Eg NullType, LowerEndpoint.
--
-- ORDERING CRITICAL
-- Ordering is critical here and should be exactly as shown here.
-- Eg AlternativeTypeList - The longer production group with comma is to be
-- tried first. Also within that production group NamedType is to be tried
-- first to avoid going into a infinite recursion.
--
-- IGNORED
-- This production is ignored as parsing another production covers this
-- production too. Eg DurationRange is covered by ValueRange.

-- LOCAL ADDITION
DEFINITIONS             ::= "DEFINITIONS"
BEGIN                   ::= "BEGIN"
END                     ::= "END"
EXPLICIT                ::= "EXPLICIT"
IMPLICIT                ::= "IMPLICIT"
AUTOMATIC               ::= "AUTOMATIC"
INSTRUCTIONS            ::= "INSTRUCTIONS"
TAGS                    ::= "TAGS"
EXTENSIBILITY           ::= "EXTENSIBILITY"
IMPLIED                 ::= "IMPLIED"
ASN_EXPORTS             ::= "EXPORTS"
ALL                     ::= "ALL"
ASN_IMPORTS             ::= "IMPORTS"
FROM                    ::= "FROM"
BOOLEAN                 ::= "BOOLEAN"
TRUE                    ::= "TRUE"
FALSE                   ::= "FALSE"
INTEGER                 ::= "INTEGER"
ENUMERATED              ::= "ENUMERATED"
REAL                    ::= "REAL"
BIT                     ::= "BIT"
STRING                  ::= "STRING"
CONTAINING              ::= "CONTAINING"
OCTET                   ::= "OCTET"
ASN_NULL                ::= "NULL"
SEQUENCE                ::= "SEQUENCE"
DEFAULT                 ::= "DEFAULT"
OPTIONAL                ::= "OPTIONAL"
COMPONENTS              ::= "COMPONENTS"
OF                      ::= "OF"
SET                     ::= "SET"
CHOICE                  ::= "CHOICE"
UNIVERSAL               ::= "UNIVERSAL"
APPLICATION             ::= "APPLICATION"
PRIVATE                 ::= "PRIVATE"
OBJECT                  ::= "OBJECT"
ASN_IDENTIFIER          ::= "IDENTIFIER"
RELATIVE_OID            ::= "RELATIVE-OID"
OID_IRI                 ::= "OID-IRI"
RELATIVE_OID_IRI        ::= "RELATIVE-OID-IRI"
EMBEDDED                ::= "EMBEDDED"
PDV                     ::= "PDV"
EXTERNAL                ::= "EXTERNAL"
TIME                    ::= "TIME"
DATE                    ::= "DATE"
TIME_OF_DAY             ::= "TIME-OF-DAY"
DATE_TIME               ::= "DATE-TIME"
DURATION                ::= "DURATION"
BMPString               ::= "BMPString"
GeneralString           ::= "GeneralString"
GraphicString           ::= "GraphicString"
IA5String               ::= "IA5String"
ISO646String            ::= "ISO646String"
NumericString           ::= "NumericString"
PrintableString         ::= "PrintableString"
TeletexString           ::= "TeletexString"
T61String               ::= "T61String"
UniversalString         ::= "UniversalString"
UTF8String              ::= "UTF8String"
VideotexString          ::= "VideotexString"
VisibleString           ::= "VisibleString"
CHARACTER               ::= "CHARACTER"
EXCEPT                  ::= "EXCEPT"
UNION                   ::= "UNION"
INTERSECTION            ::= "INTERSECTION"
ASN_INCLUDES            ::= "INCLUDES"
MIN                     ::= "MIN"
MAX                     ::= "MAX"
SIZE                    ::= "SIZE"
WITH                    ::= "WITH"
COMPONENT               ::= "COMPONENT"
PRESENT                 ::= "PRESENT"
ABSENT                  ::= "ABSENT"
PATTERN                 ::= "PATTERN"
SETTINGS                ::= "SETTINGS"
PLUS_INFINITY           ::= "PLUS-INFINITY"
MINUS_INFINITY          ::= "MINUS-INFINITY"
NOT_A_NUMBER            ::= "NOT-A-NUMBER"

-- LOCAL MODIFICATION
ModuleDefinition ::=
  ModuleIdentifier
  DEFINITIONS
  EncodingReferenceDefault
  TagDefault
  ExtensionDefault
  "::="
  BEGIN
  ModuleBody
  --EncodingControlSections
  END

ModuleIdentifier ::= modulereference DefinitiveIdentification

-- ORDERING CRITICAL
DefinitiveIdentification ::=
    DefinitiveOIDandIRI
  | DefinitiveOID
  | empty

DefinitiveOID ::= "{" DefinitiveObjIdComponentList "}"

DefinitiveOIDandIRI ::= DefinitiveOID IRIValue

DefinitiveObjIdComponentList ::=
    DefinitiveObjIdComponent
  | DefinitiveObjIdComponent DefinitiveObjIdComponentList

-- ORDERING CRITICAL
DefinitiveObjIdComponent ::=
    DefinitiveNumberForm
  | DefinitiveNameAndNumberForm
  | NameForm

DefinitiveNumberForm ::= number

DefinitiveNameAndNumberForm ::= identifier "(" DefinitiveNumberForm ")"

-- LOCAL MODIFICATION
EncodingReferenceDefault ::= EncodingReferencePrime INSTRUCTIONS | empty

TagDefault ::=
    EXPLICIT TAGS
  | IMPLICIT TAGS
  | AUTOMATIC TAGS
  | empty

ExtensionDefault ::=
    EXTENSIBILITY IMPLIED
  | empty

ModuleBody ::=
    Exports Imports AssignmentList
  | empty

-- ORDERING CRITICAL
Exports ::=
    ASN_EXPORTS ALL ";"
  | ASN_EXPORTS SymbolsExported ";"
  | empty

SymbolsExported ::= SymbolList | empty

Imports ::=
    ASN_IMPORTS SymbolsImported ";"
  | empty

SymbolsImported ::= SymbolsFromModuleList | empty

SymbolsFromModuleList ::=
    SymbolsFromModule
  | SymbolsFromModuleList SymbolsFromModule

SymbolsFromModule ::= SymbolList FROM GlobalModuleReference

GlobalModuleReference ::= modulereference AssignedIdentifier

AssignedIdentifier ::=
    ObjectIdentifierValue
  | DefinedValue
  | empty

SymbolList ::=
    Symbol
  | SymbolList "," Symbol

Symbol ::=
    Reference
--  | ParameterizedReference

Reference ::=
    typereference
  | valuereference
--  | objectclassreference
--  | objectreference
--  | objectsetreference

AssignmentList ::=
    Assignment
  | AssignmentList Assignment

Assignment ::=
    TypeAssignment
  | ValueAssignment
--  | XMLValueAssignment
  | ValueSetTypeAssignment
--  | ObjectClassAssignment
--  | ObjectAssignment
--  | ObjectSetAssignment
--  | ParameterizedAssignment

DefinedType ::=
    ExternalTypeReference
  | typereference
--  | ParameterizedType
--  | ParameterizedValueSetType

DefinedValue ::=
    ExternalValueReference
  | valuereference

--NonParameterizedTypeName ::=
--    ExternalTypeReference
--  | typereference
--  | xmlasn1typename

ExternalTypeReference ::= modulereference "." typereference

ExternalValueReference ::= modulereference "." valuereference

--AbsoluteReference ::= "@" ModuleIdentifier "." ItemSpec

-- LOCAL MODIFICATION
-- ItemSpec ::=
--    typereference
--  | ItemId "." ComponentId
--
-- ItemId ::= ItemSpec
--
-- Both are redefined as shown below.
--ItemSpec ::=
--    typereference
--  | ComponentId "." ItemSpec

ComponentId ::=
    identifier
  | number
  | "*"

TypeAssignment ::= typereference "::=" Type

ValueAssignment ::= valuereference Type "::=" Value

--XMLValueAssignment ::= valuereference "::=" XMLTypedValue

--XMLTypedValue ::=
--    "<" & NonParameterizedTypeName ">" XMLValue "</" & NonParameterizedTypeName ">"
--  | "<" & NonParameterizedTypeName "/>"

ValueSetTypeAssignment ::= typereference Type "::=" ValueSet

ValueSet ::= "{" ElementSetSpecs "}"

-- ORDERING CRITICAL
-- LOCAL MODIFICATION
--
-- Type ::= BuiltinType | ReferencedType | ConstrainedType
--
-- ConstrainedType ::=
--   Type Constraint
-- | TypeWithConstraint
--
-- If Type first parses for ConstrainedType, it leads to a circular dependency -
-- TypeAssignment>Type>ConstrainedType>Type>ContrainedType>Type...
--
-- Eg. Val ::= BOOLEAN (FALSE) can lead to error if Type is not parsed as
-- ConstrainedType first but as BuiltinType. The Constraint remains
-- unparsed.
--
-- To avoid circular dependencies and let ConstrainedType work, we redefine as
-- shown below.
Type ::=
    BuiltinType ConstraintList
  | BuiltinType
  | ReferencedType ConstraintList
  | ReferencedType
--  | TypeWithConstraint                                              TODO

-- LOCAL ADDITION
-- See Type above
ConstraintList ::=
    Constraint
  | ConstraintList Constraint

BuiltinType ::=
    BitStringType
  | BooleanType
  | CharacterStringType
  | ChoiceType
  | DateType
  | DateTimeType
  | DurationType
  | EmbeddedPDVType
  | EnumeratedType
  | ExternalType
--  | InstanceOfType
  | IntegerType
  | IRIType
  | NullType
--  | ObjectClassFieldType
  | ObjectIdentifierType
  | OctetStringType
  | RealType
  | RelativeIRIType
  | RelativeOIDType
  | SequenceType
  | SequenceOfType
  | SetType
  | SetOfType
  | PrefixedType
  | TimeType
  | TimeOfDayType

ReferencedType ::=
    DefinedType
  | UsefulType
  | SelectionType
--  | TypeFromObject
--  | ValueSetFromObjects

NamedType ::= identifier Type

Value ::=
    BuiltinValue
--  | ReferencedValue                                                 TODO
--  | ObjectClassFieldValue

--XMLValue ::=
--    XMLBuiltinValue
--  | XMLObjectClassFieldValue

-- ORDERING CRITICAL
BuiltinValue ::=
    BitStringValue
  | BooleanValue
-- This has to be placed before CharacterStringValue
  | RelativeIRIValue
-- This has to be placed before CharacterStringValue
  | IRIValue
-- CharacterStringValue->UnrestrictedCharacterStringValue is also
-- equivalent to EmbeddedPDVValue, ExternalValue and SequenceValue
  | CharacterStringValue
  | ChoiceValue
--  | EmbeddedPDVValue
  | EnumeratedValue
--  | ExternalValue
--  | InstanceOfValue
  | NullValue
  | ObjectIdentifierValue
-- This is covered by BitStringValue
--  | OctetStringValue
  | RealValue
-- This is mostly covered under RealValue and identifier is covered under
-- EnumeratedValue
--  | IntegerValue
-- This is covered by ObjectIdentifierValue
--  | RelativeOIDValue
-- This is covered under SequenceOfValue
--  | SequenceValue
  | SequenceOfValue
-- This is covered under SequenceOfValue
--  | SetValue
-- This is covered under SequenceOfValue
--  | SetOfValue
-- This is covered by Value
--  | PrefixedValue
--  | TimeValue                                                       TODO

--XMLBuiltinValue ::=
--    XMLBitStringValue
--  | XMLBooleanValue
--  | XMLCharacterStringValue
--  | XMLChoiceValue
--  | XMLEmbeddedPDVValue
--  | XMLEnumeratedValue
--  | XMLExternalValue
--  | XMLInstanceOfValue
--  | XMLIntegerValue
--  | XMLIRIValue
--  | XMLNullValue
--  | XMLObjectIdentifierValue
--  | XMLOctetStringValue
--  | XMLRealValue
--  | XMLRelativeIRIValue
--  | XMLRelativeOIDValue
--  | XMLSequenceValue
--  | XMLSequenceOfValue
--  | XMLSetValue
--  | XMLSetOfValue
--  | XMLPrefixedValue
--  | XMLTimeValue

--ReferencedValue ::=                                                 TODO
--    DefinedValue
--  | ValueFromObject

NamedValue ::= identifier Value

--XMLNamedValue ::= "<" & identifier ">" XMLValue "</" & identifier ">"

BooleanType ::= BOOLEAN

BooleanValue ::= TRUE | FALSE

--XMLBooleanValue ::=
--    EmptyElementBoolean
--  | TextBoolean

--EmptyElementBoolean ::=
--    "<" & "true" "/>"
--  | "<" & "false" "/>"

--TextBoolean ::=
--    extended-true
--  | extended-false

-- ORDERING CRITICAL
IntegerType ::=
    INTEGER "{" NamedNumberList "}"
  | INTEGER

NamedNumberList ::=
    NamedNumber
  | NamedNumberList "," NamedNumber

NamedNumber ::=
    identifier "(" SignedNumber ")"
  | identifier "(" DefinedValue ")"

-- LOCAL MODIFICATION
SignedNumber ::=
    number
  | NegativeNumber

-- ORDERING CRITICAL
--IntegerValue ::= SignedNumber | identifier

--XMLIntegerValue ::=
--    XMLSignedNumber
--  | EmptyElementInteger
--  | TextInteger

--XMLSignedNumber ::=
--    number
--  |"-" & number

--EmptyElementInteger ::= "<" & identifier "/>"

--TextInteger ::= identifier

EnumeratedType ::= ENUMERATED "{" Enumerations "}"

-- ORDERING CRITICAL
Enumerations ::=
--    RootEnumeration "," "..." ExceptionSpec "," AdditionalEnumeration TODO
--  | RootEnumeration "," "..." ExceptionSpec
  RootEnumeration

RootEnumeration ::= Enumeration

AdditionalEnumeration ::= Enumeration

Enumeration ::=
    EnumerationItem
  | EnumerationItem "," Enumeration

-- ORDERING CRITICAL
EnumerationItem ::= NamedNumber | identifier

EnumeratedValue ::= identifier

--XMLEnumeratedValue ::=
--    EmptyElementEnumerated
--  | TextEnumerated

--EmptyElementEnumerated ::= "<" & identifier "/>"

--TextEnumerated ::= identifier

RealType ::= REAL

RealValue ::=
    NumericRealValue
  | SpecialRealValue

-- LOCAL MODIFICATION
NumericRealValue ::=
    realnumber
  | NegativeRealnumber
-- Removing below as this equivalent to plain SequenceValue
--  | SequenceValue

-- LOCAL MODIFICATION
SpecialRealValue ::=
    PLUS_INFINITY
  | MINUS_INFINITY
  | NOT_A_NUMBER

--XMLRealValue ::= XMLNumericRealValue | XMLSpecialRealValue

--XMLNumericRealValue ::=
--    realnumber
--  | "-" & realnumber

--XMLSpecialRealValue ::=
--    EmptyElementReal
--  | TextReal

--EmptyElementReal ::=
--    "<" & PLUS-INFINITY "/>"
--  | "<" & MINUS-INFINITY "/>"
--  | "<" & NOT-A-NUMBER "/>"

--TextReal ::=
--    "INF"
--  | "-" & "INF"
--  | "NaN"

-- ORDERING CRITICAL
BitStringType ::=
    BIT STRING "{" NamedBitList "}"
  | BIT STRING

NamedBitList ::=
    NamedBit
  | NamedBitList "," NamedBit

NamedBit ::=
    identifier "(" number ")"
  | identifier "(" DefinedValue ")"

-- ORDERING CRITICAL
BitStringValue ::=
    bstring
  | hstring
  | "{" IdentifierList "}"
  | "{" "}"
  | CONTAINING Value

-- ORDERING CRITICAL
IdentifierList ::=
    identifier
  | IdentifierList "," identifier

--XMLBitStringValue ::=
--    XMLTypedValue
--  | xmlbstring
--  | XMLIdentifierList
--  | empty

--XMLIdentifierList ::=
--    EmptyElementList
--  | TextList

--EmptyElementList ::=
--    "<" & identifier "/>"
--  | EmptyElementList "<" & identifier "/>"

--TextList ::=
--    identifier
--  | TextList identifier

OctetStringType ::= OCTET STRING

-- IGNORED
--OctetStringValue ::=
--    bstring
--  | hstring
--  | CONTAINING Value

--XMLOctetStringValue ::=
--    XMLTypedValue
--  | xmlhstring

-- LOCAL MODIFICATION
NullType ::= ASN_NULL

-- LOCAL MODIFICATION
NullValue ::= ASN_NULL

--XMLNullValue ::= empty

SequenceType ::=
    SEQUENCE "{" "}"
--  | SEQUENCE "{" ExtensionAndException OptionalExtensionMarker "}"  TODO
  | SEQUENCE "{" ComponentTypeLists "}"

-- ORDERING CRITICAL
--ExtensionAndException ::= "..." ExceptionSpec | "..."

-- LOCAL MODIFICATION
--OptionalExtensionMarker ::= "," Ellipsis | empty

Ellipsis ::= "..."

ComponentTypeLists ::=
    RootComponentTypeList
--  | RootComponentTypeList "," ExtensionAndException ExtensionAdditions OptionalExtensionMarker                       TODO
--  | RootComponentTypeList "," ExtensionAndException ExtensionAdditions ExtensionEndMarker "," RootComponentTypeList
--  | ExtensionAndException ExtensionAdditions ExensionEndMarker "," RootComponentTypeList
--  | ExtensionAndException ExtensionAdditions OptionalExtensionMarker

RootComponentTypeList ::= ComponentTypeList

ExtensionEndMarker ::= "," "..."

--ExtensionAdditions ::=
--    "," ExtensionAdditionList
--  | empty

--ExtensionAdditionList ::=
--    ExtensionAddition
--  | ExtensionAdditionList "," ExtensionAddition

--ExtensionAddition ::=
--    ComponentType
--  | ExtensionAdditionGroup

--ExtensionAdditionGroup ::= "[[" VersionNumber ComponentTypeList "]]"

-- ORDERING CRITICAL
--VersionNumber ::= number ":" | empty

ComponentTypeList ::=
    ComponentType
  | ComponentTypeList "," ComponentType

-- ORDERING CRITICAL
ComponentType ::=
    NamedType DEFAULT Value
  | NamedType OPTIONAL
  | NamedType
  | COMPONENTS OF Type

SequenceValue ::=
    "{" ComponentValueList "}"
  | "{" "}"

ComponentValueList ::=
    NamedValue
  | ComponentValueList "," NamedValue

--XMLSequenceValue ::=
--    XMLComponentValueList
--  | empty

--XMLComponentValueList ::=
--    XMLNamedValue
--  | XMLComponentValueList XMLNamedValue

-- ORDERING CRITICAL
SequenceOfType ::= SEQUENCE OF Type | SEQUENCE OF NamedType

SequenceOfValue ::=
    "{" ValueList "}"
  | "{" NamedValueList "}"
  | "{" "}"

ValueList ::=
    Value
  | ValueList "," Value

NamedValueList ::=
    NamedValue
  | NamedValueList "," NamedValue

--XMLSequenceOfValue ::=
--    XMLValueList
--  | XMLDelimitedItemList
--  | empty

--XMLValueList ::=
--    XMLValueOrEmpty
--  | XMLValueOrEmpty XMLValueList

--XMLValueOrEmpty ::=
--    XMLValue
--  | "<" & NonParameterizedTypeName "/>"

--XMLDelimitedItemList ::=
--    XMLDelimitedItem
--  | XMLDelimitedItem XMLDelimitedItemList

--XMLDelimitedItem ::=
--    "<" & NonParameterizedTypeName ">" XMLValue "</" & NonParameterizedTypeName ">"
--  | "<" & identifier ">" XMLValue "</" & identifier ">"

SetType ::=
    SET "{" "}"
--  | SET "{" ExtensionAndException OptionalExtensionMarker "}"       TODO
  | SET "{" ComponentTypeLists "}"

-- IGNORED
--SetValue ::=
--    "{" ComponentValueList "}"
--  | "{" "}"

--XMLSetValue ::=
--    XMLComponentValueList
--  | empty

SetOfType ::= SET OF Type | SET OF NamedType

-- IGNORED
--SetOfValue ::=
--    "{" ValueList "}"
--  | "{" NamedValueList "}"
--  | "{" "}"

--XMLSetOfValue ::=
--    XMLValueList
--  | XMLDelimitedItemList
--  | empty

ChoiceType ::= CHOICE "{" AlternativeTypeLists "}"

AlternativeTypeLists ::=
    RootAlternativeTypeList
--  | RootAlternativeTypeList "," ExtensionAndException ExtensionAdditionAlternatives OptionalExtensionMarker          TODO

RootAlternativeTypeList ::= AlternativeTypeList

--ExtensionAdditionAlternatives ::=
--    "," ExtensionAdditionAlternativesList
--  | empty

--ExtensionAdditionAlternativesList ::=
--    ExtensionAdditionAlternative
--  | ExtensionAdditionAlternativesList "," ExtensionAdditionAlternative

--ExtensionAdditionAlternative ::=
--    ExtensionAdditionAlternativesGroup
--  | NamedType

--ExtensionAdditionAlternativesGroup ::= "[[" VersionNumber AlternativeTypeList "]]"

AlternativeTypeList ::=
    NamedType
  | AlternativeTypeList "," NamedType

ChoiceValue ::= identifier ":" Value

--XMLChoiceValue ::= "<" & identifier ">" XMLValue "</" & identifier ">"

SelectionType ::= identifier "<" Type

PrefixedType ::=
    TaggedType
  | EncodingPrefixedType

-- IGNORED
--PrefixedValue ::= Value

--XMLPrefixedValue ::= XMLValue

EncodingPrefixedType ::= EncodingPrefix Type

EncodingPrefix ::=
  "[" EncodingReference
--      EncodingInstruction
  "]"

-- ORDERING CRITICAL
TaggedType ::=
    Tag EXPLICIT Type
  | Tag IMPLICIT Type
  | Tag Type

Tag ::= "[" EncodingReference Class ClassNumber "]"

-- LOCAL MODIFICATION
EncodingReference ::=
    EncodingReferencePrime ":"
  | empty

ClassNumber ::=
    number
  | DefinedValue

Class ::=
    UNIVERSAL
  | APPLICATION
  | PRIVATE
  | empty

-- LOCAL MODIFICATION
ObjectIdentifierType ::= OBJECT ASN_IDENTIFIER

-- ORDERING CRITICAL
ObjectIdentifierValue ::=
    "{" DefinedValue ObjIdComponentsList "}"
  | "{" ObjIdComponentsList "}"

ObjIdComponentsList ::=
    ObjIdComponents
  | ObjIdComponents ObjIdComponentsList

-- ORDERING CRITICAL
-- DefinedValue is covered inside NumberForm
ObjIdComponents ::=
    NameAndNumberForm
  | NameForm
  | NumberForm
--  | DefinedValue

NameForm ::= identifier

NumberForm ::= number | DefinedValue

NameAndNumberForm ::= identifier "(" NumberForm ")"

--XMLObjectIdentifierValue ::= XMLObjIdComponentList

--XMLObjIdComponentList ::=
--    XMLObjIdComponent
--  | XMLObjIdComponent & "." & XMLObjIdComponentList

-- ORDERING CRITICAL
--XMLObjIdComponent ::=
--    NameForm
--  | XMLNameAndNumberForm
--  | XMLNumberForm

--XMLNumberForm ::= number

--XMLNameAndNumberForm ::= identifier & "(" & XMLNumberForm & ")"

-- LOCAL MODIFICATION
RelativeOIDType ::= RELATIVE_OID

-- IGNORED
--RelativeOIDValue ::= "{" RelativeOIDComponentsList "}"

-- IGNORED
--RelativeOIDComponentsList ::=
--    RelativeOIDComponents
--  | RelativeOIDComponents RelativeOIDComponentsList

-- IGNORED
-- ORDERING CRITICAL
-- DefinedValue is covered inside NumberForm
--RelativeOIDComponents ::=
--    NameAndNumberForm
--  | NumberForm
--  | DefinedValue

--XMLRelativeOIDValue ::= XMLRelativeOIDComponentList

--XMLRelativeOIDComponentList ::=
--    XMLRelativeOIDComponent
--  | XMLRelativeOIDComponent & "." & XMLRelativeOIDComponentList

-- ORDERING CRITICAL
--XMLRelativeOIDComponent ::=
--    XMLNameAndNumberForm
--  | XMLNumberForm

-- LOCAL MODIFICATION
IRIType ::= OID_IRI

IRIValue ::= """ FirstArcIdentifier SubsequentArcIdentifier """

FirstArcIdentifier ::= "/" ArcIdentifier

SubsequentArcIdentifier ::=
    "/" ArcIdentifier SubsequentArcIdentifier
  | empty

ArcIdentifier ::=
    integerUnicodeLabel
  | non-integerUnicodeLabel

--XMLIRIValue ::= FirstArcIdentifier SubsequentArcIdentifier

-- LOCAL MODIFICATION
RelativeIRIType ::= RELATIVE_OID_IRI

RelativeIRIValue ::= """ FirstRelativeArcIdentifier SubsequentArcIdentifier """

FirstRelativeArcIdentifier ::= ArcIdentifier

--XMLRelativeIRIValue ::= FirstRelativeArcIdentifier SubsequentArcIdentifier

EmbeddedPDVType ::= EMBEDDED PDV

-- IGNORED
--EmbeddedPDVValue ::= SequenceValue

--XMLEmbeddedPDVValue ::= XMLSequenceValue

ExternalType ::= EXTERNAL

-- IGNORED
--ExternalValue ::= SequenceValue

--XMLExternalValue ::= XMLSequenceValue

TimeType ::= TIME

--TimeValue ::= tstring                                               TODO

--XMLTimeValue ::= xmltstring

DateType ::= DATE

-- LOCAL MODIFICATION
TimeOfDayType ::= TIME_OF_DAY

-- LOCAL MODIFICATION
DateTimeType ::= DATE_TIME

DurationType ::= DURATION

CharacterStringType ::=
    RestrictedCharacterStringType
  | UnrestrictedCharacterStringType

CharacterStringValue ::=
    RestrictedCharacterStringValue
-- Removing below as this equivalent to plain SequenceValue
--  | UnrestrictedCharacterStringValue

--XMLCharacterStringValue ::=
--    XMLRestrictedCharacterStringValue
--  | XMLUnrestrictedCharacterStringValue

RestrictedCharacterStringType ::=
    BMPString
  | GeneralString
  | GraphicString
  | IA5String
  | ISO646String
  | NumericString
  | PrintableString
  | TeletexString
  | T61String
  | UniversalString
  | UTF8String
  | VideotexString
  | VisibleString

RestrictedCharacterStringValue ::=
    cstring
  | CharacterStringList
  | Quadruple
  | Tuple

CharacterStringList ::= "{" CharSyms "}"

CharSyms ::=
    CharsDefn
  | CharSyms ","  CharsDefn

CharsDefn ::=
    cstring
  | Quadruple
  | Tuple
  | DefinedValue

Quadruple ::= "{" Group "," Plane "," Row "," Cell "}"

Group ::= number

Plane ::= number

Row ::= number

Cell ::= number

Tuple ::= "{" TableColumn "," TableRow "}"

TableColumn ::= number

TableRow ::= number

--XMLRestrictedCharacterStringValue ::= xmlcstring

UnrestrictedCharacterStringType ::= CHARACTER STRING

-- IGNORED
--UnrestrictedCharacterStringValue ::= SequenceValue

--XMLUnrestrictedCharacterStringValue ::= XMLSequenceValue

UsefulType ::=
    GeneralizedTime
  | UTCTime
  | ObjectDescriptor

GeneralizedTime ::= "GeneralizedTime"

UTCTime ::= "UTCTime"

ObjectDescriptor ::= "ObjectDescriptor"

TypeWithConstraint ::=
    SET Constraint OF Type
  | SET SizeConstraint OF Type
  | SEQUENCE Constraint OF Type
  | SEQUENCE SizeConstraint OF Type
  | SET Constraint OF NamedType
  | SET SizeConstraint OF NamedType
  | SEQUENCE Constraint OF NamedType
  | SEQUENCE SizeConstraint OF NamedType

Constraint ::= "(" ConstraintSpec ExceptionSpec ")"

ConstraintSpec ::=
    SubtypeConstraint
--  | GeneralConstraint

SubtypeConstraint ::= ElementSetSpecs

-- ORDERING CRITICAL
ElementSetSpecs ::=
    RootElementSetSpec "," "..." "," AdditionalElementSetSpec
  | RootElementSetSpec "," Ellipsis
  | RootElementSetSpec

RootElementSetSpec ::= ElementSetSpec

AdditionalElementSetSpec ::= ElementSetSpec

ElementSetSpec ::=
    Unions
  | ALL Exclusions

-- This is manually generated for now
--
-- Unions ::=
--     Intersections
--   | UElems UnionMark Intersections
--
-- UElems ::= Unions
--
-- Combining above two productions into a single production as shown below.
--
-- Unions ::=
--     Unions UnionMark Intersections
--   | Intersections

-- This is manually generated for now
--
--Intersections ::=
--    IElems IntersectionMark IntersectionElements
--  | IntersectionElements
--
-- IElems ::= Intersections
--
-- Combining above two productions into a single production as shown below.
--
-- Intersections ::=
--    Intersections IntersectionMark IntersectionElements
--  | IntersectionElements

-- ORDERING CRITICAL
IntersectionElements ::=
    Elems Exclusions
  | Elements

Elems ::= Elements

Exclusions ::= EXCEPT Elements

UnionMark ::= "|" | UNION

IntersectionMark ::= "^" | INTERSECTION

Elements ::=
    SubtypeElements
--  | ObjectSetElements
  | "(" ElementSetSpec ")"

-- ORDERING CRITICAL
SubtypeElements ::=
    ContainedSubtype
  | ValueRange
-- This is added after ValueRange to prevent SingleValue from wrongly
-- consuming values meant for ValueRange
  | SingleValue
  | PermittedAlphabet
  | SizeConstraint
-- Gets consumed via ContainedSubtype
--  | TypeConstraint
  | InnerTypeConstraints
  | PatternConstraint
  | PropertySettings
-- These are same as ValueRange
--  | DurationRange
--  | TimePointRange
--  | RecurrenceRange

SingleValue ::= Value

ContainedSubtype ::= Includes Type

Includes ::= ASN_INCLUDES | empty

ValueRange ::= LowerEndpoint ".." UpperEndpoint

-- ORDERING CRITICAL
-- LOCAL MODIFICATION
LowerEndpoint ::= LowerEndValue LessThan | LowerEndValue

-- ORDERING CRITICAL
-- LOCAL MODIFICATION
UpperEndpoint ::= LessThan UpperEndValue | UpperEndValue

-- LOCAL ADDITION
LessThan ::= "<"

LowerEndValue ::= Value | MIN

UpperEndValue ::= Value | MAX

SizeConstraint ::= SIZE Constraint

TypeConstraint ::= Type

PermittedAlphabet ::= FROM Constraint

InnerTypeConstraints ::=
    WITH COMPONENT SingleTypeConstraint
  | WITH COMPONENTS MultipleTypeConstraints

SingleTypeConstraint ::= Constraint

MultipleTypeConstraints ::=
    FullSpecification
  | PartialSpecification

FullSpecification ::= "{" TypeConstraints "}"

PartialSpecification ::= "{" "..." "," TypeConstraints "}"

TypeConstraints ::=
    NamedConstraint
  | NamedConstraint "," TypeConstraints

NamedConstraint ::= identifier ComponentConstraint

ComponentConstraint ::= ValueConstraint PresenceConstraint

ValueConstraint ::= Constraint | empty

PresenceConstraint ::= PRESENT | ABSENT | OPTIONAL | empty

PatternConstraint ::= PATTERN Value

-- LOCAL MODIFICATION
-- See 51.10.1
PropertySettings ::= SETTINGS """ PropertySettingsList """

PropertySettingsList ::=
    PropertyAndSettingPair
  | PropertySettingsList PropertyAndSettingPair

PropertyAndSettingPair ::= PropertyName "=" SettingName

PropertyName ::= psname

SettingName ::= psname

-- IGNORED
--DurationRange ::= ValueRange

-- IGNORED
--TimePointRange ::= ValueRange

-- IGNORED
--RecurrenceRange ::= ValueRange

ExceptionSpec ::= "!" ExceptionIdentification | empty

ExceptionIdentification ::=
    SignedNumber
  | DefinedValue
  | Type ":" Value
