/*
 * This is a test asn1 module. Lots of funny comments to try and break
 * the parser.
 */

-- TestModule
-- TestModule

--Module Under Test--SimpleTypeTest { abc def } DEFINITIONS----::=----
----BEGIN -- module begin

-- # -- SimpleTypeTestBool   ::= BOOLEAN   -- bool builtin type
-- # -- SimpleTypeTestInt    ::= INTEGER   -- integer builtin type

/*bla/*bla/**/bla*/bla*/

----END -- module end

-- TestModule
-- TestModule
